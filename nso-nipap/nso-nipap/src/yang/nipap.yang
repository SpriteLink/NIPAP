module nipap {

  namespace "http://spritelink.net/nipap/settings";
  prefix nipap;

  import ietf-inet-types {
    prefix inet;
  }

  import tailf-common {
    prefix tailf;
  }

  import tailf-ncs {
    prefix ncs;
  }

  grouping prefix-attributes {

    leaf customer_id {
      description "Customer identifier";
      type string;
      }

    leaf description {
      description "Description of prefix";
      type string;
    }

    leaf node {
      description "Node, e.g. FQDN";
      type string;
    }

    leaf order_id {
      description "Order identifier";
      type string;
    }
  }

  grouping response-grouping {
    container response {
      description "CDB Subscriber will write the response here";
      config false;
      tailf:cdb-oper {
        tailf:persistent true;
        }

      leaf status {
        config false;
        tailf:cdb-oper {
          tailf:persistent true;
          }
        type enumeration {
          enum ok;
          enum error;
        }
      }

      leaf status-message {
        config false;
        tailf:cdb-oper {
          tailf:persistent true;
          }
        type string;
      }

      leaf prefix {
        type inet:ip-prefix;
        config false;
        tailf:cdb-oper {
          tailf:persistent true;
        }
      }

      leaf prefix_id {
        type uint32;
        config false;
        tailf:cdb-oper {
          tailf:persistent true;
        }
      }
      uses prefix-attributes;
    }
  }

  augment /ncs:services {
    description "NIPAP settings";

    container nipap {

      list backend {
        description "Connectivity setting for a NIPAP backend";

        key name;
        leaf name {
          tailf:info "Backend id";
          tailf:cli-allow-range;
          type string;
        }

        leaf hostname {
          description "Hostname of NIPAP backend";
          type inet:host;
          mandatory true;
        }
        leaf port {
          description "Port that NIPAP backend listens on";
          type inet:port-number;
          default 1337;
        }
        leaf username {
          description "Username to authenticate with NIPAP backend";
          type string;
          mandatory true;
        }
        leaf password {
          description "Password to authenticate with NIPAP backend";
          // should we use type passwdStr isntead?
          type string;
          mandatory true;
        }
        leaf default {
          type boolean;
          default true;
//          must "count(../backend/default) <= 1";
          // TODO: make sure only one backend is marked as default
        }
      }

      list from-pool {
        key name;
        leaf name {
          tailf:info "Name of pool to request prefix from";
          tailf:cli-allow-range;
          type string;
        }

        list request {
          key name;
          leaf name {
            tailf:info "Request name";
            tailf:cli-allow-range;
            type string;
          }

          container attributes {
            description "Prefix attributes";
            uses prefix-attributes;
          }

          container arguments {
            description "Prefix arguments to the request";

            leaf family {
              description "Address family";
              default '4';
              type enumeration {
                enum 4 {
                  value 4;
                }
                enum 6 {
                  value 6;
                }
              }
            }

            leaf prefix-length {
              description "Prefix length";
              type uint8;
            }
          }

          list from-prefix-request {
            description "Request prefix from the requested prefix";
            key name;
            ordered-by user;
            leaf name {
              description "Uniqe identifier for the prefix";
              type string;
              }

            container attributes {
              description "Prefix attributes";
              uses prefix-attributes;
            }

            uses response-grouping;
            }

            uses response-grouping;

            leaf redeploy-service {
              description "Redeploy service after succesful allocation";
              type string;
            }
        }
      }
    }
  }
}
